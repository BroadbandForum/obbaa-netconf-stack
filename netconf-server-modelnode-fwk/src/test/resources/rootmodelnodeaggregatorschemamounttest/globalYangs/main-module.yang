module main-module {
  yang-version 1.1;

  namespace "ns:ns";
  prefix "mm";

  import ietf-yang-schema-mount {
    prefix yangmnt;
  }

  revision 2019-03-13;

  container root {
    container mp {
      yangmnt:mount-point "mp";
    }
  }
}
