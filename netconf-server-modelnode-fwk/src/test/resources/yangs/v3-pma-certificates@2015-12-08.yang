module v3-pma-certificates {

	yang-version 1;

	namespace "test:v3-pma-certificates";

	prefix "pma-cert";

    import v3-certificates { prefix "cert"; }
    revision "2015-12-08" {
        description "Test.";
        reference "";
    }


    augment "/cert:certificate-mgmt" {
        container pma-certs {
            list certificate {
                    description
                        "A list of X 509 certificates.";
                    key id;

                    leaf id {
                        type string;
                        description
                            "Unique id of the certificate.";
                        }

                    ordered-by system;

                    leaf cert-binary {
                        type string;
                        description
                            "The binary certificate structure as specified by RFC 5246, Section 7.4.6, i.e.,: opaque ASN.1Cert<1..2^24>";
                        reference
                            "RFC 5246: The Transport Layer Security (TLS)
                            Protocol Version 1.2";
                    }
            }
    	}

    }
}
