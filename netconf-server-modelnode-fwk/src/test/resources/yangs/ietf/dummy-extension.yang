module dummy-extensions {
    yang-version 1;
     
    namespace "http://www.test-company.com/solutions/anv-yang-extensions";
    prefix "anvext";
     
    description "YANG extensions to be used in PMA";
     
    revision "2016-01-07" {
        description "Initial version.";
    }  
 
	extension  treat-as-relative-path {
		description
			"Indicates the absolute path is augment with device-specific path and the relative path has to be validated";
	}

	extension big-list {
            description
                "The big-list statement can be added to a list to indicate that
                un-filtered retrieval of the entries in this list will lead to
                a big response or a too-big rpc error.";
    }
    
    extension is-password {
        description
            "We can apply this to the password leaf in ANV. Values marked as 
             passwords in the YANG model will be replaced by ******** in the protocol tracing";
    }
    
    extension is-sensitive {
        description
            "We can apply this to the sensitive data in ANV. Values marked as 
             sensitive in the YANG model will be replaced by ##<hash value>## in the protocol tracing. 
             And this setting can be configurable to get the actual values in tracing";
    }
}
