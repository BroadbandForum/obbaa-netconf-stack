module example-jukebox-with-is-password-ext {

    yang-version 1;

    namespace
      "http://example.com/ns/example-jukebox-with-is-password-ext";

    prefix jbox;

    import dummy-extensions {
      prefix "anvext";
      revision-date "2016-01-07";
    }

    organization "Example, Inc.";

    contact "support at example.com";

    description
      "Example Jukebox Data Model Module";

    revision "2014-07-03" {
      description "Initial version.";
      reference
        "example.com document 1-4673";

    }


    identity genre {
      description "Base for all genre types";
    }

    identity alternative {
      base genre;
      description "Alternative music";
    }

    identity blues {
      base genre;
      description "Blues music";
    }

    identity country {
      base genre;
      description "Country music";
    }

    identity jazz {
      base genre;
      description "Jazz music";
    }

    identity pop {
      base genre;
      description "Pop music";
    }

    identity rock {
      base genre;
      description "Rock music";
    }

    grouping configured-device-properties-group {
        description
                "A set of device attributes that are configured when the PMA initiates
                communication.";

        leaf username {
            type string;
            //mandatory true;
            anvext:is-sensitive;
            description
                "The username is only valid for SSH, but applicable to all authentication
                methods.";
        }

        leaf password {
            type string;
            anvext:is-password;
            description
                "The password is only valid for SSH, and applicable username-and-password
                authentication methods.";
        }
    }

 
    container jukebox {
      presence
        "An empty container indicates that the jukebox
        service is available";
      description
        "Represents a jukebox resource, with a library, playlists,
        and a play operation.";
      container library {
        description
          "Represents the jukebox library resource.";
        list artist {
          key "name password";
          description
            "Represents one artist resource within the
            jukebox library resource.";
          leaf name {
            type string {
              length "1 .. max";
            }
            description
              "The name of the artist.";
          }
          leaf password {
            type string;
            anvext:is-password;
          }

          leaf password-annotation {
              type string;
          }

          list testList1{
                key key;
                leaf key{
                    type string;
                }
                choice device-connection {
                    default call-home-with-duid;

                    case call-home-with-duid {
                        leaf duid {
                            type string;
                            default "";
                            anvext:is-sensitive;
                            description
                                "The value of the DUID (DHCP Unique Identifier)
                                as defined in RFC 3315 that uniquely identifies
                                the device.";
                        }
                    }

                    case non-call-home {
                        uses configured-device-properties-group;
                    }
                }  // choice device-connection
          	}

          list album {
            key "name";
            ordered-by user;
            description
              "Represents one album resource within one
              artist resource, within the jukebox library.";
            leaf name {
              type string {
                length "1 .. max";
              }
              description
                "The name of the album.";
            }
            leaf password {
                type string;
                anvext:is-password;
                description
                    "The password is only valid for SSH, and applicable username-and-password
                    authentication methods.";
            }

            leaf genre {
              type identityref {
                base genre;
              }
              description
                "The genre identifying the type of music on
                the album.";
            }
            leaf-list genre-password {
                type string;
                anvext:is-password;
                description "A list of singers password";
             } // leaf-list genre-password

            leaf year {
              type uint16 {
                range "1900 .. max";
              }
              description
                "The year the album was released";
            }

            container admin {
              description
                "Administrative information for the album.";
              leaf label {
                type string;
                description
                  "The label that released the album.";
              }

              leaf catalogue-number {
                type string;
                description
                  "The album's catalogue number.";
              }
            }  // container admin

            list song {
              key "name";
              description
                "Represents one song resource within one
                album resource, within the jukebox library.";
              leaf name {
                type string {
                  length "1 .. max";
                }
                description
                  "The name of the song";
              }

              leaf location {
                type string;
                mandatory true;
                description
                  "The file location string of the
                 media file for the song";
              }

              leaf format {
                type string;
                description
                  "An identifier string for the media type
                  for the file associated with the
                  'location' leaf for this entry.";
              }

              leaf length {
                type uint32;
                units "seconds";
                description
                  "The duration of this song in seconds.";
              }
              leaf-list singer {
                  type string;
                  description "A list of singers";
              } // leaf-list singer
              leaf-list singer-password {
                type string;
                anvext:is-password;
                description "A list of singers password";
              } // leaf-list singer-password
            }  // list song
          }  // list album
          list awards{
            key "name";
                description
                  "Represents awards received by this artist" ;
                leaf name {
                  type string {
                    length "1 .. max";
                  }
                  description
                    "The name of the award.";
                }

          } // list awards
        }  // list artist
      }  // container library

      list playlist {
        key "name";
        description
          "Example configuration data resource";
        leaf name {
          type string;
          description
            "The name of the playlist.";
        }

        leaf description {
          type string;
          description
            "A comment describing the playlist.";
        }

        list song {
          key "index";
          ordered-by user;
          description
            "Example nested configuration data resource";
          leaf index {
            type uint32;
            description
              "An arbitrary integer index for this
              playlist song.";
          }
        }  // list song
      }  // list playlist

      leaf name {
        type string;
        description
          "Name of the jukebox";
      }


      container player {
        description
          "Represents the jukebox player resource.";
        leaf gap {
          type decimal64 {
            fraction-digits 1;
            range "0.0 .. 2.0";
          }
          units "tenths of seconds";
          description
            "Time gap between each song";
        }
      }  // container player
    }  // container jukebox

    rpc play {
      description
        "Control function for the jukebox player";
      input {
        leaf playlist {
          type string;
          mandatory true;
          description "playlist name";
        }

        leaf song-number {
          type uint32;
          mandatory true;
          description
            "Song number in playlist to play";
        }
      }
    }  // rpc play
  }  // module example-jukebox-with-is-password-ext
