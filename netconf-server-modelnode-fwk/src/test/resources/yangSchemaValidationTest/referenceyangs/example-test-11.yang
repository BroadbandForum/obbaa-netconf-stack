module example-test-11 {

    yang-version 1.1;

    namespace
      "http://example.com/ns/example-test-11";

    prefix test;

    organization "Example, Inc.";

    contact "support at example.com";

    description
      "Example Data Model Module";

    revision "2017-02-14" {
      description "Initial version.";
      reference
        "example.com document 1-4673";

    }
        
    container player {
        leaf gap {
          type decimal64 {
            fraction-digits 1;
            range "0.0 .. 2.0";
          }
          units "tenths of seconds";
          description
            "Time gap between each song";
        }
        
        action container-action {
            input {
                leaf container-action-leaf {
                    type string;
                }
            }
        }
        choice testChoice {
        	case testCase1{
        		container actionContainer {
        			action actionInChoice {
			            input {
			                leaf testInput {
			                    type string;
			                }
			            }
			        }
        		}
        		choice nestedTestChoice {
        			case nestedTestCase {
        				container containerInNestedChoice{
        					leaf test{
        						type string;
        					}
        				}
        			}
        		}
        	}
        }
        
        notification container-notification {
            leaf container-notification-leaf {
                type string;
            }
        }
    }  // container player
    
    notification root-notification {
        leaf root-notification-leaf {
            type string;
        }
    }

  }  // module example-test-11
