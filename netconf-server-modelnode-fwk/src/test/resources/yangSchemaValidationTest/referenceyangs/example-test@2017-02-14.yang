module example-test {

    yang-version 1;

    namespace
      "http://example.com/ns/example-test";

    prefix test;

    organization "Example, Inc.";

    contact "support at example.com";

    description
      "Example Data Model Module";

    revision "2017-02-14" {
      description "Initial version.";
      reference
        "example.com document 1-4673";

    }
    
    include "example-test-submodule";
    
    container player {
        leaf gap {
          type decimal64 {
            fraction-digits 1;
            range "0.0 .. 2.0";
          }
          units "tenths of seconds";
          description
            "Time gap between each song";
        }
    }  // container player

  }  // module example-test
