module idref-typedef {
     yang-version 1.1;
     namespace "http://example.com/ns/idref-typedef";
     prefix idref;

     revision 2020-05-27 {
         description
             "Initial Revision";
         reference
         "example.com";
     }

     identity idref-yang-identity {
     }

     identity idref1-yang {
         base idref-yang-identity;
     }

     identity idref2-yang {
         base idref-yang-identity;
     }

}
