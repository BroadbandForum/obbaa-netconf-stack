module sample {
     yang-version 1.1;
     namespace "http://example.com/ns/sample";
     prefix sample;
     import ordered-by-user-for-idref-and-union {
          prefix test;
     }
     revision 2020-05-27 {
         description
             "Initial Revision";
         reference
         "example.com";
     }

     identity sample-identity {
          base test:test-identity;
     }

     identity sample-idref1 {
         base sample-identity;
     }

     identity sample-idref2 {
         base sample-identity;
     }
}
