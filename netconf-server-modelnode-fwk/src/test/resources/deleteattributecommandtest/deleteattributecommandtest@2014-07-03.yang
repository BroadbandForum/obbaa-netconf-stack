module deleteattributecommandtest {
  yang-version 1;
  namespace "unit:test:dact";
  prefix dact;

  revision 2014-07-03 {
    description
      "Initial version.";
  }

  identity gender;

  identity male {
    base dact:gender;
  }

  identity female {
    base dact:gender;
  }

  container family {
    container father {
      leaf name {
        type string;
      }
      leaf gender {
        default "dact:male";
        type identityref {
          base dact:gender;
        }
      }
      
      leaf dress {
    	  default "white";
    	  type string;
    	  when "../name = 'father'";
      }

      leaf shoes {
          default "black";
          type string;
      }

      uses goggles {
        when "../dress='blue'";
      }
    }
    container mother {
      leaf name {
        type string;
      }
      leaf husband-name {
        default "/dact:family/dact:father/dact:name";
        type instance-identifier {
          require-instance false;
        }
      }
      leaf gender {
        default "dact:female";
        type identityref {
          base dact:gender;
        }
      }
    }
  }

  augment '/dact:family/dact:father' {
    when "name = 'father'";
    leaf shirt-size {
        type uint8 {
          range "0..100";
        }

      default "40";
    }
  }

  grouping goggles {
    leaf goggles{
        type string;
        default "rayban";
    }
  }
}
