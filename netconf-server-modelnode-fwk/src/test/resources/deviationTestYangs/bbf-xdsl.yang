module bbf-xdsl {

  namespace "urn:broadband-forum-org:yang:bbf-xdsl";  
  prefix xdsl;
  
  import ietf-interfaces {
    prefix if;
  }
  
  import bbf-if-type {
    prefix bbfift;
  }
  
  organization 
    "TBD";
    
  contact 
    "TBD";
    
  description 
    "A YANG module which defines management objects related to 
     an interface which may support one or more DSL or G.fast
     technologies";
  
  revision 2016-01-25 {
    description 
      "Initial revision.";
    reference
      "TBD";
  }
  
  identity xdsl-mode {
    description
      "Base identity for xDSL modes";
  }
  
  identity mode-fast {
    base xdsl-mode;
    description
      "ITU-T G.9701 G.fast";
  }

  identity mode-vdsl {
    base xdsl-mode;
    description
      "ITU-T G.993.2 VDSL2 or derived technology";
  }
  
  typedef xdsl-mode-ref {
    type identityref {
      base xdsl-mode;
    }
    description
      "Reference to an xDSL mode of operation";
  }
  
  augment "/if:interfaces/if:interface" {
    when "if:type = 'bbfift:xdsl'" {
      description
        "Only applicable when the interface type is 'xdsl'";
    }
    description 
      "Data nodes for the configuration of xDSL lines.";

    container line {
      presence 
        "If present, indicates that the interface is able to operate
         according to the appropriate ITU-T specification for one
         or more DSL or G.fast technologies";
      description 
        "Line configuration data for xDSL interfaces.";
        
      leaf-list supported-mode {
        type xdsl-mode-ref;
        must "(count(../configured-mode) = 0) or " +
             "(../configured-mode = ../supported-mode)" {
          description
            "If configured modes of operation are specified, each
             mode must be part of the supported modes";
        }
        config false;
        min-elements 1;
        description
          "Supported mode(s) of operation";
      }
      
      leaf-list configured-mode {
        type xdsl-mode-ref;
        description
          "Configured mode(s) of operation. An empty list indicates
           that the configured mode is undetermined";
      }
    }
  }

  augment "/if:interfaces-state/if:interface" {
    when "if:type = 'bbfift:xdsl'" {
      description
        "Only applicable when the interface type is 'xdsl'";
    }
    description 
      "Data nodes for the operational state of xDSL lines.";
      
    container line {
      presence 
        "If present, indicates that the interface is able to operate
         according to the appropriate ITU-T specification for one
         or more DSL or G.fast technologies";
      description 
        "Line state data for FAST interfaces.";
        
      leaf operational-mode {
        type union {
          type enumeration {
            enum undetermined {
              description
                "The current mode of operation is undetermined. This 
                 is most likely due to the fact that G.hs has not 
                 completed the first time";
            }
          }
          type xdsl-mode-ref;
        }
        description
          "Current mode of operation. Upon initialization, the mode
           will be undetermined until G.hs successfully completes
           for the first time.";
      }
    }
  }
}
