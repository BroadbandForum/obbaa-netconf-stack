module nc-stack-extensions {
    yang-version 1;

    namespace "http://www.test-company.com/solutions/nc-stack-extensions";
    prefix "ncext";

    description "YANG extensions to be used in applicaitons on top of NC stack";

    revision "2020-09-09" {
        description "New extension statement for user management and access restrictions.";
    }

    revision "2020-04-15" {
        description "New extension statement for user management and access restrictions.";
    }

    revision "2019-11-01" {
        description 
          "Add support for validation hints";
        reference "kafka";
    }
    
    revision "2018-06-28" {
        description "Initial version.";
    }

    extension requires-permission {
        description
          "This indicates that while accessing the yang elements which follows this statement requires a specific user scope defined in the Idenitity Management System. When there is no explicit extension statement specified, then the system expects that user has NBI_RESIDUAL scope.";
        argument target-scope;
    }

    extension big-list {
        description
            "The big-list statement can be added to a list to indicate that
            un-filtered retrieval of the entries in this list will lead to
            a big response or a too-big rpc error.";
    }
    extension searchable {
        description
            "The searchable statement can be added to a list to indicate that
            the list can be searched using the like queries";
    }

    extension validation-hints {
        argument hints;
    }

    extension referring-node-is-under-changed-node {
        argument constraint;
    }

    extension ual-disabled {
        description
            "The ual-disabled statement can be added to a RPC or action to indicate that
            the RPC should not be logged in user activity log.";
    }
    extension ual-application {
        description
          "This statement can be added to a list to indicate that the list belongs to the application specified in the argument application-name.";
        argument application-name;
    }
}
