module augment-module2 {
  yang-version 1.1;
  namespace "aug:module2";
  prefix am2;

  import ietf-interfaces {
    prefix if;
  }

  revision 2019-07-28;

  augment "/if:interfaces" {
    leaf tag {
      type string;
    }
  }
}
