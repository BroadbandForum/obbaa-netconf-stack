module example-jukebox-types {

     yang-version 1;

     namespace
       "http://example.com/ns/example-jukebox-types";

     prefix ejt;

     organization "Example, Inc.";

     contact "support at example.com";

     description
       "Example Jukebox Data Model Module";

     revision "2014-07-03" {
       description "Initial version.";
       reference
         "example.com document 1-4673";

     }

     identity genre {
       description "Base for all genre types";
     }

     identity blues {
       base genre;
       description "Blues music";
     }

     identity country {
       base genre;
       description "Country music";
     }

     identity dummy-id-ref{
        description "Base for all dummy-id-ref attribute under album";
     }

     identity dummy-id-ref1 {
        base dummy-id-ref;
        description "dummy-id-ref1";
     }

     identity dummy-id-ref2 {
        base dummy-id-ref;
        description "dummy-id-ref2";
     }


}
