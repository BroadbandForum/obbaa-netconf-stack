module module-with-invalid-hint4 {
  namespace "urn:module-with-invalid-hint4";
  prefix modulehint;

  revision 2018-06-28 {
    description
      "Initial version.";
  }
    
  import nc-stack-extensions {
      prefix "ncext";
  }
  
  import module-with-node-hints {
      prefix "nodehints";
  }
  
  ncext:validation-hints "/nodehints:hintContainer/nodehints:nodeWithHint3" {
      ncext:expression "../nodeWithHint4='hello' and ../nodeWithHint5='test'" ;
      ncext:hints "";
      ncext:description "The impact of nodeWithHint4 and nodeWithHint5 is nodeWithHint3";
  }
  
}
