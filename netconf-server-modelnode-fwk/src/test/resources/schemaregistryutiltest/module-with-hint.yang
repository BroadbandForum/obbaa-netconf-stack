module module-with-hint {
  namespace "urn:module-with-hint";
  prefix modulehint;
  
  revision 2018-06-28 {
    description
      "Initial version.";
  }
    
  import nc-stack-extensions {
      prefix "ncext";
  }
  
  import module-with-node-hints {
      prefix "nodehints";
  }

  import augmenting-module-with-when-condition{
    prefix "amwwc";
  }
  
  ncext:validation-hints "/nodehints:hintContainer/nodehints:nodeWithHint1" {
      ncext:expression "derived-from-or-self 
          (../nodehints:nodeWithHint2, 'identity3')" ;
      ncext:hints "*->SKIP_IMPACT_ON_CREATE";
      ncext:description "The impact of nodeWithHint2 should be checked only when it is deleted or modified";
  }
  
  ncext:validation-hints "/nodehints:hintContainer/nodehints:nodeWithHint3" {
      ncext:expression "../nodeWithHint4='hello' and ../nodeWithHint5='test'" ;
      ncext:hints "/nodehints:hintContainer/nodehints:nodeWithHint4->SKIP_IMPACT_ON_CREATE /nodehints:hintContainer/nodehints:nodeWithHint5->SKIP_IMPACT_VALIDATION";
      ncext:description "The impact of nodeWithHint4 and nodeWithHint5 is nodeWithHint3";
  }
  
  ncext:validation-hints "/nodehints:hintContainer/nodehints:nodeWithHint8" {
      ncext:expression "count(../nodehints:nodeLeafList)=2" ;
      ncext:hints "/nodehints:hintContainer/nodehints:nodeLeafList->SKIP_VALIDATION";
  }

  ncext:validation-hints " /nodehints:hintContainer/amwwc:augmented-container " {
      ncext:expression "/nodehints:hintContainer/nodehints:type= 'augmentable'" ;
      ncext:hints "*->SKIP_IMPACT_ON_CREATE";
      ncext:description "have deliberately put spaces in line 40 in the scheam path";
  }
}
