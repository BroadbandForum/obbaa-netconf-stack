module module-with-invalid-hint2 {
  namespace "urn:module-with-invalid-hint2";
  prefix modulehint;

  revision 2018-06-28 {
    description
      "Initial version.";
  }
    
  import nc-stack-extensions {
      prefix "ncext";
  }
  
  import module-with-node-hints {
      prefix "nodehints";
  }
  
  ncext:validation-hints "/nodehints:hintContainer/nodehints:nodeWithHint1" {
      ncext:expression "derived-from-or-self 
          (../nodehints:nodeWithHint2, 'identity4')" ;
      ncext:hints "*->SKIP_IMPACT_ON_CREATE";
  }
  
}
