module thirdparty-module3 {

  namespace "urn:thirdparty-module3";
    prefix tp1;

  organization "TBD";
  contact
    "TBD";
  description
    "This module contains a collection of YANG definitions for
     managing top level FAST configuration and augmenations to
     ietf-interfaces.";

  revision 2016-02-10 {
      description
        "Initial revision.";
      reference "TBD";
  }
}
