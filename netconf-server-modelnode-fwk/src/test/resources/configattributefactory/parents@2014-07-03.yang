module parents {
  yang-version 1;
  namespace "unit:test:caft:parents";
  prefix dactp;

  revision 2014-07-03 {
    description
      "Initial version.";
  }

  identity gender;

  identity male {
    base gender;
  }

  identity female {
    base gender;
  }

  container family {
    container father {
      leaf name {
        type string;
      }
      leaf gender {
        default "male";
        type identityref {
          base gender;
        }
      }
    }
    container mother {
      leaf name {
        type string;
      }
      leaf husband-name {
        default "/family/father/name";
        type instance-identifier {
          require-instance false;
        }
      }
      leaf gender {
        default "female";
        type identityref {
          base gender;
        }
      }
    }
  }
}
