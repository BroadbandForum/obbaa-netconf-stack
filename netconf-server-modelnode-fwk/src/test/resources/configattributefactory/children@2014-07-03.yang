module children {
  yang-version 1;
  namespace "unit:test:caft:children";
  prefix dactc;

 import parents {
    prefix dactp;
  }

  import occupation {
      prefix dacto;
    }

  revision 2014-07-03 {
    description
      "Initial version.";
  }

  container family {
    container son {
      leaf name {
        type string;
      }
      leaf gender {
        default "dactp:male";
        type identityref {
          base dactp:gender;
        }
      }
    }
    container daughter {
      leaf name {
        type string;
      }
      leaf father-name {
        default "/dactp:family/dactp:father/dactp:name";
        type instance-identifier {
          require-instance false;
        }
      }
      leaf father-occupation {
          default "/dactp:family/dactp:father/dacto:occupation";
          type instance-identifier {
            require-instance false;
          }
        }
      leaf gender {
        default "dactp:female";
        type identityref {
          base dactp:gender;
        }
      }
    }
  }
}
