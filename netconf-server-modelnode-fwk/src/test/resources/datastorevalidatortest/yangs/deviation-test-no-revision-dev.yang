module deviation-test-no-revision-dev {
	
	yang-version 1;
    
	namespace "urn:org:bbf2:pma:deviation:test";
	
	prefix "devTest";
	
	import feature-test { prefix "feat"; }
	
	deviation "/feat:test/feat:leaf1" {
	    deviate add {
	        must "true()";
	    }
	}
}
