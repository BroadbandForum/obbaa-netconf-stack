module forwarders{
    
    yang-version 1.1;
    
    namespace "test-forwarders";
    
    prefix "bbf-l2-fwd";
    
    revision "2019-11-07" {
        description "Initial version.";
     }
    
    import test-interfaces {
        prefix if;
    }
    
    typedef interface-usage {
        type enumeration {
          enum "user-port" {
            description
              "The interface having this interface usage connects the 
               Access Node to a user.";
          }
          enum "network-port" {
            description
              "The interface having this interface usage connects the 
               Access Node to a network.";
          }
          enum "subtended-node-port" {
            description
              "The interface having this interface usage connects the 
               Access Node to a another Access Node.";
          }
          enum "inherit" {
            description
              "The interface usage is not defined for this interface.
               Instead the interface usage is inherited from the interface
               usage of the lower-layer interface. If no interface-usage 
               is specified at the lowest level of an interface stack, 
               then the default is product and interface specific.";
          }
        }
        description
          "This type identifies the position of the interface in the 
           network. Access Nodes are typically asymetric: some interfaces 
           connect users to the Access Node while other interfaces connect
           the Access Node to the network.

           For some functionality of the Access Node the position of the 
           interface matters.";
      }
    
    container forwarders{
        
        list forwarder{

            must "not(boolean(/if:interfaces/if:interface[if:name = current()/bbf-l2-fwd:ports/bbf-l2-fwd:port/bbf-l2-fwd:sub-interface and bbf-if-usg:interface-usage/bbf-if-usg:interface-usage = 'user-port']))";

            must "current()/bbf-l2-fwd:if-name = 'sample'";
            
            key name;
            
            leaf name{
                type string;
            }

            leaf if-name {
                type string;
                default "sample";
            }
            
            container ports{
                list port{
                    key name;
                    
                    leaf name{
                        type string;
                    }
                    
                    leaf sub-interface {
                        type if:interface-ref;
                        must
                          "derived-from-or-self(
                           /if:interfaces/if:interface[if:name = current()]
                           /if:type, 'ieee80211' )" {
                          description
                            "The type of interface being referenced MUST be a
                             vlan-sub-interface.";
                        }
                        description
                          "The VLAN sub-interface associated with this port.";
                      }
                      leaf leaf1 {
                      	type interface-usage;
                      }
                      leaf leaf2 {
                      	 must "not(boolean(../leaf1 = 'subtended-node-port'))" {
					          error-message "Name should not be test!";
					      }
					      type string;
                      }
                    
                }
            }
        }
        
        list test-forwarder{

            must "(not(boolean(/if:interfaces/if:interface[if:name = current()/bbf-l2-fwd:ports/bbf-l2-fwd:port/bbf-l2-fwd:sub-interface and bbf-if-usg:interface-usage/bbf-if-usg:interface-usage = 'user-port'])) or "      
                            +"not(boolean(/if:interfaces/if:interface[if:name = current()/bbf-l2-fwd:ports/bbf-l2-fwd:port/bbf-l2-fwd:sub-interface and bbf-if-usg:interface-usage/bbf-if-usg:interface-usage = 'network-port'])) or  "
                            +"not(boolean(/if:interfaces/if:interface[if:name = current()/bbf-l2-fwd:ports/bbf-l2-fwd:port/bbf-l2-fwd:sub-interface and bbf-if-usg:interface-usage/bbf-if-usg:interface-usage = 'subtended-node-port'])))";

            must "current()/bbf-l2-fwd:if-name = 'sample'";
            
            key name;
            
            leaf name{
                type string;
            }

            leaf if-name {
                type string;
                default "sample";
            }
            
            container ports{
                list port{
                    key name;
                    
                    leaf name{
                        type string;
                    }
                    
                    leaf sub-interface {
                        type if:interface-ref;
                        must
                          "derived-from-or-self(
                           /if:interfaces/if:interface[if:name = current()]
                           /if:type, 'ieee80211' )" {
                          description
                            "The type of interface being referenced MUST be a
                             vlan-sub-interface.";
                        }
                        description
                          "The VLAN sub-interface associated with this port.";
                      }
                    
                }
            }
        }
    }
    
    augment '/if:interfaces/if:interface' {
        
        description
          "Augments interfaces with nodes relative to interface usage.";

        container interface-usage {
          description
            "Provides the interface with an interface usage.";

          leaf interface-usage {
            type interface-usage;
            description
              "Identifies the position of the interface in the network.";
          }
        }
      }
}
