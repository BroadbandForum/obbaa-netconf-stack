module interface-ref {
    
    yang-version 1.1;
    
    namespace "https://interface-ref";
    
    prefix "if-ref";
    
    import test-interfaces {
        prefix if;
    }
    
    revision "2017-04-20" {
	      description "Initial version.";
	}
    
    typedef interface-type-ref {
        type leafref {
          path "/if:interfaces/if:interface/if:type";
        }
        
    }
    
 	container tconts-config {
 		
        uses tconts-config-data;
    }

    
    grouping tconts-config-data{
    	list tcont{
    		key name;
    		
    		leaf name{
    			type string;
    		}
    		
    		leaf interface-ref{
    			type interface-type-ref;
    		}
    	}
    }
    
}
