// Contents of "datastore-validator-augment-test"
module datastore-validator-augment-test {
    yang-version 1;

    namespace "urn:opendaylight:datastore-validator-augment-test";
    prefix "validation-augment";

    import datastore-validator-test { prefix "validation"; }

    revision 2018-03-07 {
        description "Initial revision";
    }

    augment "/validation:validation/validation:test-interfaces" {
        container use-test-interface {
            leaf channel-leaf {
                type string;
            }

            leaf sample-leaf {
                type validation:test-interface-ref;
                must "/validation:validation/validation:test-interfaces/validation:test-interface[validation:name=current()]/validation:type='sampleType1'" {
                    error-message "must reference a channel-leaf";
                }
            }
        }
    }
    
    augment "/validation:validation/validation:mustOnEmptyTypeLeaf" {
    	leaf emptyTypeLeaf {
			type empty;
		}
		leaf mustOnEmptyLeaf{
			must "boolean(current()/../emptyTypeLeaf)";
			type string;
		}
		
		leaf stringLeaf {
			type string;
		}
		leaf mustOnStringLeaf{
			must "boolean(current()/../stringLeaf)";
			type string;
		}
		leaf-list leafList{
			type string;
		}
		leaf mustOnLeafList{
			must "boolean(current()/../leafList)";
			type string;
		}
    }

    augment "/validation:testNotification/validation:notif-container" {
        leaf sample-leaf {
            type validation:test-interface-ref;
            must "/validation:validation/validation:test-interfaces/validation:test-interface[validation:name=current()]/validation:type='sampleType1'" {
               error-message "must reference a channel-leaf";
            }
        }
    }
    
    augment "/validation:validation/validation:sampleContainer/validation:innerContainer" {
    	when "../master = 'sample'";
        leaf innerMostLeaf {
            type string;
        }
    }
}
