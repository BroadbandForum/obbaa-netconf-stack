// Contents of "commonrootchildtwo"
module commonrootchildtwo {
    namespace "urn:opendaylight:commonrootchildtwo";
    prefix "commonrootchildtwo";
    
    import commonroot{
    	prefix "commonroot";
    }

    revision 2018-05-17 {
        description "Initial revision";
    }
    
    augment "/commonroot:root-container"{
    	container subroot {
    		leaf test{
    			type string;
    		}
    	}
    }

}
