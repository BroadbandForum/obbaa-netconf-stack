module augment-container {
  yang-version 1;

      namespace
        "http://example.com/ns/example-jukebox-augment";

      prefix jbox-ag;

      import example-jukebox {
        prefix jbox;
      }

      organization "Example, Inc.";

      contact "support at example.com";

      description
        "Example Jukebox Data Model Module with container augment with different namespace";

      revision "2014-07-03" {
        description "Initial version.";
        reference
          "example.com document 1-4673";

      }

  augment "/jbox:jukebox" {
    list service {
      description
        "Dummy service under jukebox";
      key "type";
      leaf type {
        description
          "A type that identifies the type of service.";
        type string;
      }
    }
  }
}
